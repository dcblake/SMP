-- @(#) sm_usefulTypes.asn 
SmUsefulTypes DEFINITIONS ::=
BEGIN

--
 AlgorithmIdentifierVDA      ::=   SEQUENCE {
    algorithm       OBJECT IDENTIFIER,
    parameters      ANY OPTIONAL }

-- Name ::= CHOICE {
--    rDNSequence RDNSequence 
-- }


--################################
-- FROM x501if.asn
-- DistinguishedName ::= RDNSequence

-- RDNSequence ::= SEQUENCE OF RelativeDistinguishedName

-- RelativeDistinguishedName ::= SET SIZE (1..MAX) OF
--    AttributeTypeAndDistinguishedValue


-- AttributeTypeAndDistinguishedValue ::= SEQUENCE {
--    type                      OBJECT IDENTIFIER,
--    value                     ANY,
--    primaryDistinguished      BOOLEAN DEFAULT TRUE,
--    valuesWithContext         SET SIZE (1 .. MAX) OF SEQUENCE {
--    distingAttrValue          OBJECT IDENTIFIER OPTIONAL,
--    contextList               SET SIZE (1 .. MAX) OF ANY } OPTIONAL
-- }


--################################
-- DEFINE OIDs common to all operations....

   sha-1 OBJECT IDENTIFIER ::= { iso(1) identified-organization(3)
       oiw(14) secsig(3) algorithm(2) 26 }

   id-dsa OBJECT IDENTIFIER ::=
      {iso(1) member-body(2) us(840) x9-57(10040) x9cm(4) 1 }

   id-dsa-with-sha1 OBJECT IDENTIFIER ::=  { iso(1) member-body(2)
       us(840) x9-57 (10040) x9cm(4) 3 }
   id-OIW-secsig-algorithm-dsa OBJECT IDENTIFIER ::= { iso(1) identified-organization(3)
       oiw(14) secsig(3) algorithm(2) 12 }


   -- RWC; 3/23/01;
   id-SHA256 	OBJECT IDENTIFIER ::= 
	{joint-iso-itu-t(2) country(16) us(840) organization(1) gov(101) csor(3) nistalgorithm(4) 
	  hashalgs(2) 1 }
	
	id-SHA384  OBJECT IDENTIFIER  ::=  { joint-iso-itu-t(2)
               country(16) us(840) organization(1) gov(101)
               csor(3) nistalgorithm(4) hashalgs(2) 2 }
   
   -- PL: may not be correct oids            
   id-ecdsa-with-SHA256 OBJECT IDENTIFIER ::= {1 2 840 10045 4 2}
   id-ecdsa-with-SHA384 OBJECT IDENTIFIER ::= {1 2 840 10045 4 3}
   -- PL: may not be correct oids
               
   sha256WithRSAEncryption OBJECT IDENTIFIER ::= {iso(1) member-body(2) us(840) 
	  rsadsi(113549) pkcs(1) 1 11}

   sha-1WithRSAEncryption-ALT OBJECT IDENTIFIER ::= { 1 3 14 3 2 29 }

   rc2-cbc OBJECT IDENTIFIER ::= { iso(1) member-body(2) us(840)
       rsadsi(113549) encryptionAlg(3) 2 }

   id-alg-CMSRC2wrap OBJECT IDENTIFIER ::= { iso(1) member-body(2)
       us(840) rsadsi(113549) pkcs(1) pkcs-9(9) smime(16) alg(3) 7 }

-- ** Signature algorithms **

md2WithRSAEncryption OBJECT IDENTIFIER ::=
    {iso(1) member-body(2) us(840) rsadsi(113549) pkcs(1) pkcs-1(1) 2}
--        (The parameters field must be present and is defined as an 
--        ASN.1 NULL type. Implementations should also accept identifiers
--        where the parameters field is absent.)

md5WithRSAEncryption OBJECT IDENTIFIER ::=
    {iso(1) member-body(2) us(840) rsadsi(113549) pkcs(1) pkcs-1(1) 4}
--        (The parameters field must be present and is defined as an 
--        ASN.1 NULL type. Implementations should also accept identifiers
--        where the parameters field is absent.)

sha-1WithRSAEncryption OBJECT IDENTIFIER ::=
    {iso(1) member-body(2) us(840) rsadsi(113549) pkcs(1) pkcs-1(1) 5}
--        (The parameters field must be present and is defined as an 
--        ASN.1 NULL type. Implementations should also accept identifiers
--        where the parameters field is absent.)




--################################
-- From sm_VDASupport_asn.asn
-- _______________________________ NIST AES Definitions __________________________________
-- NIST-AES { joint-iso-ccitt(2) country(16) us(840) organization(1) gov(101) csor(3) nistalgorithm(4) 
--   modules (0) aes (1) } DEFINITIONS IMPLICIT TAGS ::= BEGIN

-- IMPORTS None --

-- EXPORTS All --


-- RWC;11/21/00;AESAlgorithmIdentifier ::= AlgorithmIdentifier { AES-Algorithms }


-- Algorithm information objects --

-- RWC;11/21/00;AES-Algorithms ALGORITHM ::= {
-- RWC;11/21/00;   AES-128-Algorithms  |
-- RWC;11/21/00;   AES-192-Algorithms  |
-- RWC;11/21/00;   AES-256-Algorithms,
-- RWC;11/21/00;}

-- RWC;11/21/00;AES-128-Algorithms ALGORITHM ::= {
-- RWC;11/21/00;   aes-128-ECB  |
-- RWC;11/21/00;   aes-128-CBC  |
-- RWC;11/21/00;   aes-128-OFB  |
-- RWC;11/21/00;   aes-128-CFB
-- RWC;11/21/00;}

-- RWC;11/21/00;aes-128-ECB ALGORITHM ::= { OID id-aes128-ECB }
-- RWC;11/21/00;aes-128-CBC ALGORITHM ::= { OID id-aes128-CBC PARMS AES-IV }
-- RWC;11/21/00;aes-128-OFB ALGORITHM ::= { OID id-aes128-OFB PARMS AES-IV }
-- RWC;11/21/00;aes-128-CFB ALGORITHM ::= { OID id-aes128-CFB PARMS CFBParameters }

-- RWC;11/21/00;AES-192-Algorithms ALGORITHM ::= {
-- RWC;11/21/00;   aes-192-ECB  |
-- RWC;11/21/00;   aes-192-CBC  |
-- RWC;11/21/00;   aes-192-OFB  |
-- RWC;11/21/00;   aes-192-CFB
-- RWC;11/21/00;}

-- RWC;11/21/00;aes-192-ECB ALGORITHM ::= { OID id-aes192-ECB }
-- RWC;11/21/00;aes-192-CBC ALGORITHM ::= { OID id-aes192-CBC PARMS AES-IV }
-- RWC;11/21/00;aes-192-OFB ALGORITHM ::= { OID id-aes192-OFB PARMS AES-IV }
-- RWC;11/21/00;aes-192-CFB ALGORITHM ::= { OID id-aes192-CFB PARMS CFBParameters }

-- RWC;11/21/00;AES-256-Algorithms ALGORITHM ::= {
-- RWC;11/21/00;   aes-256-ECB  |
-- RWC;11/21/00;   aes-256-CBC  |
-- RWC;11/21/00;   aes-256-OFB  |
-- RWC;11/21/00;   aes-256-CFB
-- RWC;11/21/00;}

-- RWC;11/21/00;aes-256-ECB ALGORITHM ::= { OID id-aes256-ECB }
-- RWC;11/21/00;aes-256-CBC ALGORITHM ::= { OID id-aes256-CBC PARMS AES-IV }
-- RWC;11/21/00;aes-256-OFB ALGORITHM ::= { OID id-aes256-OFB PARMS AES-IV }
-- RWC;11/21/00;aes-256-CFB ALGORITHM ::= { OID id-aes256-CFB PARMS CFBParameters }


-- Parameter definitions --


-- ASN.1 Type to handle either old or new DSS parameters

OldOrNewParametersVDA	::= CHOICE {
	newParams	DSAWithSHA1Parameters,
	oldParams	Kea-Dss-ParmsVDA
}


-- THE FOLLOWING definitions are used to handle DSS parameters 
-- from a V1 certificate's SubjectPublicKeyInfo
--

Kea-Dss-ParmsVDA	::= CHOICE  {
		different-ParmsVDA [0]	Different-ParmsVDA,
		common-Parms [1] Common-Parms  }

Dss-ParmsVDA	::= SEQUENCE  {
	p	OCTET STRING,
	q	OCTET STRING,
	g	OCTET STRING  }

Kea-Parms	::= SEQUENCE  {
	p	OCTET STRING,
	q	OCTET STRING,
	g	OCTET STRING  }

Different-ParmsVDA	::= SEQUENCE  {
					kea-Parms Kea-Parms,
					dss-ParmsVDA Dss-ParmsVDA  }

Common-Parms	::= SEQUENCE  {
	p	OCTET STRING,
	q	OCTET STRING,
	g	OCTET STRING  }


DSAWithSHA1Parameters ::= SEQUENCE
{
    p  INTEGER,
    q  INTEGER,
    g  INTEGER
}

CFBParameters ::= SEQUENCE {
   aes-IV        AES-IV,
   numberOfBits	 NumberOfBits
}

AES-IV ::= OCTET STRING (SIZE(16))

NumberOfBits ::= INTEGER(1..128)


-- AES information object identifiers -- 

csor OBJECT IDENTIFIER ::= { 
   joint-iso-itu-t(2) country(16) us(840) organization(1) gov(101) 3 }

nistAlgorithms OBJECT IDENTIFIER ::= { csor nistAlgorithm(4) } 

aes OBJECT IDENTIFIER ::= { nistAlgorithms  1 }

-- 128 bit AES information object identifiers -- 

id-aes128-ECB OBJECT IDENTIFIER ::= { aes 1 }
id-aes128-CBC OBJECT IDENTIFIER ::= { aes 2 }
id-aes128-OFB OBJECT IDENTIFIER ::= { aes 3 }
id-aes128-CFB OBJECT IDENTIFIER ::= { aes 4 }

id-aes128-wrap  OBJECT IDENTIFIER  ::=  { aes 5 }

-- 192 bit AES information object identifiers -- 

id-aes192-ECB OBJECT IDENTIFIER ::= { aes 21 }
id-aes192-CBC OBJECT IDENTIFIER ::= { aes 22 }
id-aes192-OFB OBJECT IDENTIFIER ::= { aes 23 }
id-aes192-CFB OBJECT IDENTIFIER ::= { aes 24 }

id-aes192-wrap  OBJECT IDENTIFIER  ::=  { aes 25 }

-- 256 bit AES information object identifiers -- 

id-aes256-ECB OBJECT IDENTIFIER ::= { aes 41 } 
id-aes256-CBC OBJECT IDENTIFIER ::= { aes 42 }  
id-aes256-OFB OBJECT IDENTIFIER ::= { aes 43 } 
id-aes256-CFB OBJECT IDENTIFIER ::= { aes 44 }

id-aes256-wrap  OBJECT IDENTIFIER  ::=  { aes 45 }

id-md2 OBJECT IDENTIFIER ::= 
   {iso(1) member-body(2) us(840) rsadsi(113549) digestAlgorithm(2) 2}


-- Triple DES Parameters, contains IV

TDESParameters ::= OCTET STRING

RC2-CBC-parameter ::=  SEQUENCE {
      rc2ParameterVersion  INTEGER,
      iv                   OCTET STRING (8)}

RC2CBCParameter ::= SEQUENCE {
     rc2ParameterVersion INTEGER,
     iv OCTET STRING  }  -- exactly 8 octets

-- RWC; From pkix1 specification.
Dss-Sig-ValueVDA  ::=  SEQUENCE  {
    r             INTEGER,
    s             INTEGER}


--###############################
-- DEFINE RSAES_OAEP definitions (from RFC2437)

   pkcs-1VDA OBJECT IDENTIFIER ::=
      {iso(1) member-body(2) us(840) rsadsi(113549) pkcs(1) pkcs-1(1) }

   id-RSAES-OAEP OBJECT IDENTIFIER ::= {pkcs-1VDA 7}

   RSAES-OAEP-params ::=  SEQUENCE {
     hashFunc [0] AlgorithmIdentifierVDA --RWC;{{oaepDigestAlgorithms}}
       OPTIONAL, --RWC;DEFAULT Sha1Identifier,
     maskGenFunc [1] AlgorithmIdentifierVDA --RWC;{{pkcs1MGFAlgorithms}}
       OPTIONAL, --RWC;DEFAULT Mgf1SHA1Identifier,
     pSourceFunc [2] AlgorithmIdentifierVDA
       --RWC;{{Pkcs1pSourceAlgorithms}}
       OPTIONAL } --RWC;DEFAULT PSpecifiedEmptyIdentifier }

   --RWC;oaepDigestAlgorithms ALGORITHM-IDENTIFIER ::= {
   --RWC;  {NULL IDENTIFIED BY id-sha1} }

   id-sha1 OBJECT IDENTIFIER ::=
     {iso(1) identified-organization(3) oiw(14) secsig(3)
       algorithms(2) 26}

   --RWC;sha1Identifier ::= AlgorithmIdentifier {id-sha1, NULL}

   --RWC;pkcs1MGFAlgorithms ALGORITHM-IDENTIFIER ::= {
   --RWC;{AlgorithmIdentifier {{oaepDigestAlgorithms}} IDENTIFIED
   --RWC;                     BY id-mgf1} }

   id-mgf1 OBJECT IDENTIFIER ::= {pkcs-1VDA 8}

   --RWC;mgf1SHA1Identifier ::= AlgorithmIdentifier {
   --RWC;id-mgf1, sha1Identifier }

   --RWC;pkcs1pSourceAlgorithms ALGORITHM-IDENTIFIER ::= {
   --RWC;  {OCTET STRING IDENTIFIED BY id-pSpecified} }

   id-pSpecified OBJECT IDENTIFIER ::= {pkcs-1VDA 9}

   --RWC;pSpecifiedEmptyIdentifier ::= AlgorithmIdentifier {
   --RWC;       id-pSpecified, OCTET STRING SIZE (0) }

--################################
-- From x501ud
--dsVDA OBJECT IDENTIFIER   ::=    { joint-iso-ccitt ds(5) }
--attributeTypeVDA OBJECT IDENTIFIER   ::=    {dsVDA 4}
--id-atVDA OBJECT IDENTIFIER   ::=   attributeTypeVDA

--################################
-- From x520sa
--RWC;id-at-countryName    OBJECT IDENTIFIER   ::=   {id-atVDA 6}
--RWC;id-at-localityName    OBJECT IDENTIFIER   ::=   {id-atVDA 7}
--RWC;id-at-commonName    OBJECT IDENTIFIER   ::=   {id-atVDA 3}
--RWC;id-at-surname    OBJECT IDENTIFIER   ::=   {id-atVDA 4}
--RWC;id-at-organizationName    OBJECT IDENTIFIER   ::=   {id-atVDA 10}
--RWC;id-at-organizationalUnitName   OBJECT IDENTIFIER   ::=   {id-atVDA 11}



END
