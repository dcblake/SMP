ORAddressModule	-- From MTSAbstractService { joint-iso-itu-t mhs(6) mts(3)
				-- modules(0) mts-abstract-service(1) version-1999(1) }

DEFINITIONS IMPLICIT TAGS ::=

BEGIN

-- EXPORTS ALL --

IMPORTS
	PresentationAddress, X121Address -- REN 12/19/03 Temp Inclusion of X121Address
		FROM SelectedAttributeTypes ;


ORAddress ::= --snacc isPdu:"TRUE" -- SEQUENCE {
	built-in-standard-attributes		BuiltInStandardAttributes,
	built-in-domain-defined-attributes	BuiltInDomainDefinedAttributes OPTIONAL,
	-- see also teletex-domain-defined-attributes
	extension-attributes				ExtensionAttributes OPTIONAL }

--	The OR-address is semantically absent from the OR-name if the built-in-standard-attribute
--	sequence is empty and the built-in-domain-defined-attributes and extension-attributes are both omitted.


--	Built-in Standard Attributes

BuiltInStandardAttributes ::= SEQUENCE {
	country-name					CountryName OPTIONAL,
	administration-domain-name		AdministrationDomainName OPTIONAL,
	network-address				[0] NetworkAddress OPTIONAL,
	-- see also extended-network-address
	terminal-identifier			[1] TerminalIdentifier OPTIONAL,
	private-domain-name			[2] PrivateDomainName OPTIONAL,
	organization-name			[3] OrganizationName OPTIONAL,
	-- see also teletex-organization-name
	numeric-user-identifier		[4] NumericUserIdentifier OPTIONAL,
	personal-name				[5] PersonalName OPTIONAL,
	-- see also teletex-personal-name
	organizational-unit-names	[6] OrganizationalUnitNames OPTIONAL
	-- see also teletex-organizational-unit-names -- }
 
CountryName ::= [APPLICATION 1] CHOICE {
	x121-dcc-code			NumericString (SIZE (ub-country-name-numeric-length)),
	iso-3166-alpha2-code	PrintableString (SIZE (ub-country-name-alpha-length)) }

AdministrationDomainName ::= [APPLICATION 2] CHOICE {
	numeric		NumericString (SIZE (0..ub-domain-name-length)),
	printable	PrintableString (SIZE (0..ub-domain-name-length)) }

NetworkAddress ::= X121Address
-- see also extended-network-address

-- REN - 12/29/03 - temporarily removed and imported to eliminate duplicate definition
-- X121Address ::= NumericString (SIZE (1..ub-x121-address-length))

TerminalIdentifier ::= PrintableString (SIZE (1..ub-terminal-id-length))

PrivateDomainName ::= CHOICE {
	numeric		NumericString (SIZE (1..ub-domain-name-length)),
	printable	PrintableString (SIZE (1..ub-domain-name-length)) }

OrganizationName ::= PrintableString (SIZE (1..ub-organization-name-length))
-- see also teletex-organization-name

NumericUserIdentifier ::= NumericString (SIZE (1..ub-numeric-user-id-length))

PersonalName ::= SET {
	surname					[0] PrintableString (SIZE (1..ub-surname-length)),
	given-name				[1] PrintableString (SIZE (1..ub-given-name-length)) OPTIONAL,
	initials				[2] PrintableString (SIZE (1..ub-initials-length)) OPTIONAL,
	generation-qualifier	[3] PrintableString (SIZE (1..ub-generation-qualifier-length))
									OPTIONAL}
-- see also teletex-personal-name

OrganizationalUnitNames ::= SEQUENCE SIZE (1..ub-organizational-units) OF
								OrganizationalUnitName
-- see also teletex-organizational-unit-names

OrganizationalUnitName ::= PrintableString (SIZE (1..ub-organizational-unit-name-length))


--	Built-in Domain-defined Attributes

BuiltInDomainDefinedAttributes ::= SEQUENCE SIZE (1..ub-domain-defined-attributes) OF 
										BuiltInDomainDefinedAttribute

BuiltInDomainDefinedAttribute ::= SEQUENCE {
	type	PrintableString (SIZE (1..ub-domain-defined-attribute-type-length)),
	value	PrintableString (SIZE (1..ub-domain-defined-attribute-value-length)) }


--	Extension Attributes

ExtensionAttributes ::= SET SIZE (1..ub-extension-attributes) OF ExtensionAttribute

ExtensionAttribute ::= SEQUENCE {
	extension-attribute-type	[0] INTEGER (0..ub-extension-attributes),
	extension-attribute-value	[1] ANY DEFINED BY extension-attribute-type }


--	Extension Standard Attributes

common-name OBJECT-TYPE	-- EXTENSION-ATTRIBUTE
	SYNTAX	CommonName
	ACCESS	read-write
	STATUS	mandatory
	::= 1

CommonName	::= PrintableString (SIZE (1..ub-common-name-length))

teletex-common-name OBJECT-TYPE	-- EXTENSION-ATTRIBUTE
	SYNTAX	TeletexCommonName
	ACCESS	read-write
	STATUS	mandatory
	::= 2

TeletexCommonName	::= TeletexString (SIZE (1..ub-common-name-length))

universal-common-name OBJECT-TYPE	-- EXTENSION-ATTRIBUTE
	SYNTAX	UniversalCommonName
	ACCESS	read-write
	STATUS	mandatory
	::= 24

UniversalCommonName	::= UniversalOrBMPString (SIZE (1..ub-common-name-length))

teletex-organization-name OBJECT-TYPE	-- EXTENSION-ATTRIBUTE
	SYNTAX	TeletexOrganizationalName
	ACCESS	read-write
	STATUS	mandatory
	::= 3

TeletexOrganizationalName	::= TeletexString (SIZE (1..ub-organization-name-length))

universal-organization-name OBJECT-TYPE	-- EXTENSION-ATTRIBUTE
	SYNTAX	UniversalOrganizationalName
	ACCESS	read-write
	STATUS	mandatory
	::= 25

UniversalOrganizationalName	::= UniversalOrBMPString (SIZE (1..ub-organization-name-length))

teletex-personal-name OBJECT-TYPE	-- EXTENSION-ATTRIBUTE
	SYNTAX	TeletexPersonalName
	ACCESS	read-write
	STATUS	mandatory
	::= 4

TeletexPersonalName	::= SET {
	surname			[0] TeletexString (SIZE (1..ub-surname-length)),
	given-name		[1] TeletexString (SIZE (1..ub-given-name-length)) OPTIONAL,
	initials		[2] TeletexString (SIZE (1..ub-initials-length)) OPTIONAL,
	generation-qualifier	[3] TeletexString (SIZE (1..ub-generation-qualifier-length)) 
								OPTIONAL }

universal-personal-name OBJECT-TYPE	-- EXTENSION-ATTRIBUTE
	SYNTAX	UniversalPersonalName
	ACCESS	read-write
	STATUS	mandatory
	::= 26

UniversalPersonalName	::= SET {
	surname			[0] UniversalOrBMPString (SIZE (1..ub-universal-surname-length)),
	--	If a language is specified within surname, then that language applies to each of the following
	--	optional components unless the component specifies another language.
	given-name		[1] UniversalOrBMPString (SIZE (1..ub-universal-given-name-length)) OPTIONAL,
	initials		[2] UniversalOrBMPString (SIZE (1..ub-universal-initials-length)) OPTIONAL,
	generation-qualifier	[3]
		UniversalOrBMPString (SIZE (1..ub-universal-generation-qualifier-length)) OPTIONAL }

teletex-organizational-unit-names OBJECT-TYPE	-- EXTENSION-ATTRIBUTE
	SYNTAX	TeletexOrganizationUnitNames
	ACCESS	read-write
	STATUS	mandatory
	::= 5

TeletexOrganizationUnitNames	::= SEQUENCE SIZE (1..ub-organizational-units) OF
										TeletexOrganizationalUnitName

TeletexOrganizationalUnitName	::= TeletexString 
									(SIZE (1..ub-organizational-unit-name-length))

universal-organizational-unit-names OBJECT-TYPE	-- EXTENSION-ATTRIBUTE
	SYNTAX	UniversalOrganizationUnitNames
	ACCESS	read-write
	STATUS	mandatory
	::= 27

UniversalOrganizationUnitNames	::= SEQUENCE SIZE (1..ub-organizational-units) OF
										UniversalOrganizationalUnitName
--	If a unit name specifies a language, then that language applies to subordinate unit names unless
--	the subordinate specifies another language.

UniversalOrganizationalUnitName	::= UniversalOrBMPString 
									(SIZE (1..ub-organizational-unit-name-length))

UniversalOrBMPString -- { INTEGER:ub-string-length } --	::= SET {
	character-encoding CHOICE {
		two-octets		BMPString (SIZE(1..MAX)),	-- {ub-string-length}
		four-octets		UniversalString (SIZE(1..MAX)) },	-- {ub-string-length}
	iso-639-language-code	PrintableString (SIZE(2|5)) OPTIONAL }

pds-name OBJECT-TYPE	-- EXTENSION-ATTRIBUTE
	SYNTAX	PDSName
	ACCESS	read-write
	STATUS	mandatory
	::= 7

PDSName	::= PrintableString (SIZE (1..ub-pds-name-length))

physical-delivery-country-name OBJECT-TYPE	-- EXTENSION-ATTRIBUTE
	SYNTAX	PhysicalDeliveryCountryName
	ACCESS	read-write
	STATUS	mandatory
	::= 8

PhysicalDeliveryCountryName	::= CHOICE	{
	x121-dcc-code			NumericString (SIZE (ub-country-name-numeric-length)),
	iso-3166-alpha2-code	PrintableString (SIZE (ub-country-name-alpha-length)) }

postal-code OBJECT-TYPE	-- EXTENSION-ATTRIBUTE
	SYNTAX	PostalCode
	ACCESS	read-write
	STATUS	mandatory
	::= 9

PostalCode	::= CHOICE {
	numericCode		NumericString (SIZE (1..ub-postal-code-length)),
	printableCode	PrintableString (SIZE (1..ub-postal-code-length))  }

physical-delivery-office-name OBJECT-TYPE	-- EXTENSION-ATTRIBUTE
	SYNTAX	PhysicalDeliveryOfficeName
	ACCESS	read-write
	STATUS	mandatory
	::= 10

PhysicalDeliveryOfficeName	::= PDSParameter

universal-physical-delivery-office-name OBJECT-TYPE	-- EXTENSION-ATTRIBUTE
	SYNTAX	UniversalPhysicalDeliveryOfficeName
	ACCESS	read-write
	STATUS	mandatory
	::= 29

UniversalPhysicalDeliveryOfficeName	::= UniversalPDSParameter

physical-delivery-office-number OBJECT-TYPE	-- EXTENSION-ATTRIBUTE
	SYNTAX	PhysicalDeliveryOfficeNumber
	ACCESS	read-write
	STATUS	mandatory
	::= 11

PhysicalDeliveryOfficeNumber	::= PDSParameter

universal-physical-delivery-office-number OBJECT-TYPE	-- EXTENSION-ATTRIBUTE
	SYNTAX	UniversalPhysicalDeliveryOfficeNumber
	ACCESS	read-write
	STATUS	mandatory
	::= 30

UniversalPhysicalDeliveryOfficeNumber	::= UniversalPDSParameter

extension-OR-address-components OBJECT-TYPE	-- EXTENSION-ATTRIBUTE
	SYNTAX	ExtensionORAddressComponents
	ACCESS	read-write
	STATUS	mandatory
	::= 12

ExtensionORAddressComponents	::= PDSParameter

universal-extension-OR-address-components OBJECT-TYPE	-- EXTENSION-ATTRIBUTE
	SYNTAX	UniversalExtensionORAddressComponents
	ACCESS	read-write
	STATUS	mandatory
	::= 31

UniversalExtensionORAddressComponents	::= UniversalPDSParameter

physical-delivery-personal-name OBJECT-TYPE	-- EXTENSION-ATTRIBUTE
	SYNTAX	PhysicalDeliveryPersonalName
	ACCESS	read-write
	STATUS	mandatory
	::= 13

PhysicalDeliveryPersonalName	::= PDSParameter

universal-physical-delivery-personal-name OBJECT-TYPE	-- EXTENSION-ATTRIBUTE
	SYNTAX	UniversalPhysicalDeliveryPersonalName
	ACCESS	read-write
	STATUS	mandatory
	::= 32

UniversalPhysicalDeliveryPersonalName	::= UniversalPDSParameter

physical-delivery-organization-name OBJECT-TYPE	-- EXTENSION-ATTRIBUTE
	SYNTAX	PhysicalDeliveryOrganizationName
	ACCESS	read-write
	STATUS	mandatory
	::= 14

PhysicalDeliveryOrganizationName	::= PDSParameter

universal-physical-delivery-organization-name OBJECT-TYPE	-- EXTENSION-ATTRIBUTE
	SYNTAX	UniversalPhysicalDeliveryOrganizationName
	ACCESS	read-write
	STATUS	mandatory
	::= 33

UniversalPhysicalDeliveryOrganizationName	::= UniversalPDSParameter

extension-physical-delivery-address-components OBJECT-TYPE	-- EXTENSION-ATTRIBUTE
	SYNTAX	ExtensionPhysicalDeliveryAddressComponents
	ACCESS	read-write
	STATUS	mandatory
	::= 15

ExtensionPhysicalDeliveryAddressComponents	::= PDSParameter

universal-extension-physical-delivery-address-components OBJECT-TYPE	-- EXTENSION-ATTRIBUTE
	SYNTAX	UniversalExtensionPhysicalDeliveryAddressComponents
	ACCESS	read-write
	STATUS	mandatory
	::= 34

UniversalExtensionPhysicalDeliveryAddressComponents	::= UniversalPDSParameter

unformatted-postal-address OBJECT-TYPE	-- EXTENSION-ATTRIBUTE
	SYNTAX	UnformattedPostalAddress
	ACCESS	read-write
	STATUS	mandatory
	::= 16

UnformattedPostalAddress	::= SET {
	printableAddress	SEQUENCE SIZE(1..ub-pds-physical-address-lines) OF 
				PrintableString (SIZE (1..ub-pds-parameter-length)) OPTIONAL,
	teletexString		TeletexString (SIZE (1..ub-unformatted-address-length)) OPTIONAL }

universal-unformatted-postal-address OBJECT-TYPE	-- EXTENSION-ATTRIBUTE
	SYNTAX	UniversalUnformattedPostalAddress
	ACCESS	read-write
	STATUS	mandatory
	::= 35

UniversalUnformattedPostalAddress	::= UniversalOrBMPString (SIZE (1..ub-unformatted-address-length))

street-address OBJECT-TYPE	-- EXTENSION-ATTRIBUTE
	SYNTAX	StreetAddress
	ACCESS	read-write
	STATUS	mandatory
	::= 17

StreetAddress	::= PDSParameter

universal-street-address OBJECT-TYPE	-- EXTENSION-ATTRIBUTE
	SYNTAX	UniversalStreetAddress
	ACCESS	read-write
	STATUS	mandatory
	::= 36

UniversalStreetAddress	::= UniversalPDSParameter

post-office-box-address OBJECT-TYPE	-- EXTENSION-ATTRIBUTE
	SYNTAX	PostOfficeBoxAddress
	ACCESS	read-write
	STATUS	mandatory
	::= 18

PostOfficeBoxAddress	::= PDSParameter

universal-post-office-box-address OBJECT-TYPE	-- EXTENSION-ATTRIBUTE
	SYNTAX	UniversalPostOfficeBoxAddress
	ACCESS	read-write
	STATUS	mandatory
	::= 37

UniversalPostOfficeBoxAddress	::= UniversalPDSParameter

poste-restante-address OBJECT-TYPE	-- EXTENSION-ATTRIBUTE
	SYNTAX	PosteRestanteAddress
	ACCESS	read-write
	STATUS	mandatory
	::= 19

PosteRestanteAddress	::= PDSParameter

universal-poste-restante-address OBJECT-TYPE	-- EXTENSION-ATTRIBUTE
	SYNTAX	UniversalPosteRestanteAddress
	ACCESS	read-write
	STATUS	mandatory
	::= 38

UniversalPosteRestanteAddress	::= UniversalPDSParameter

unique-postal-name OBJECT-TYPE	-- EXTENSION-ATTRIBUTE
	SYNTAX	UniquePostalName
	ACCESS	read-write
	STATUS	mandatory
	::= 20

UniquePostalName	::= PDSParameter

univeral-unique-postal-name OBJECT-TYPE	-- EXTENSION-ATTRIBUTE
	SYNTAX	UniversalUniquePostalName
	ACCESS	read-write
	STATUS	mandatory
	::= 39

UniversalUniquePostalName	::= UniversalPDSParameter

local-postal-attributes OBJECT-TYPE	-- EXTENSION-ATTRIBUTE
	SYNTAX	LocalPostalAttributes
	ACCESS	read-write
	STATUS	mandatory
	::= 21

LocalPostalAttributes	::= PDSParameter

universal-local-postal-attributes OBJECT-TYPE	-- EXTENSION-ATTRIBUTE
	SYNTAX	UniversalLocalPostalAttributes
	ACCESS	read-write
	STATUS	mandatory
	::= 40

UniversalLocalPostalAttributes	::= UniversalPDSParameter

PDSParameter	::= SET {
	printableString		PrintableString (SIZE (1..ub-pds-parameter-length)) OPTIONAL,
	teletexString		TeletexString (SIZE (1..ub-pds-parameter-length)) OPTIONAL }

UniversalPDSParameter	::= UniversalOrBMPString (SIZE (1..ub-pds-parameter-length))

extended-network-address OBJECT-TYPE	-- EXTENSION-ATTRIBUTE
	SYNTAX	ExtendedNetworkAddress
	ACCESS	read-write
	STATUS	mandatory
	::= 22

ExtendedNetworkAddress	::= CHOICE {
	e163-4-address	SEQUENCE  {
			number 		[0]	NumericString (SIZE (1..ub-e163-4-number-length)),
			subAddress	[1]	NumericString (SIZE (1..ub-e163-4-sub-address-length ))
							OPTIONAL  },
	psapAddress		[0]	PresentationAddress }

terminal-type OBJECT-TYPE	-- EXTENSION-ATTRIBUTE
	SYNTAX	TerminalType
	ACCESS	read-write
	STATUS	mandatory
	::= 23

TerminalType  ::=  INTEGER {
	telex		(3),
	teletex 	(4),
	g3Facsimile	(5),
	g4Facsimile	(6),
	ia5Terminal	(7),
	videotex 	(8)  } (SIZE (0..ub-integer-options))


--	Extension Domain-defined Attributes

teletex-domain-defined-attributes OBJECT-TYPE	-- EXTENSION-ATTRIBUTE
	SYNTAX	TeletexDomainDefinedAttributes
	ACCESS	read-write
	STATUS	mandatory
	::= 6

TeletexDomainDefinedAttributes	::= SEQUENCE SIZE (1..ub-domain-defined-attributes) OF
										TeletexDomainDefinedAttribute

TeletexDomainDefinedAttribute	::= SEQUENCE {
	type	TeletexString (SIZE (1..ub-domain-defined-attribute-type-length)),
	value	TeletexString (SIZE (1..ub-domain-defined-attribute-value-length)) }

universal-domain-defined-attributes OBJECT-TYPE	-- EXTENSION-ATTRIBUTE
	SYNTAX	UniversalDomainDefinedAttributes
	ACCESS	read-write
	STATUS	mandatory
	::= 28

UniversalDomainDefinedAttributes ::= SEQUENCE SIZE (1..ub-domain-defined-attributes) OF
										UniversalDomainDefinedAttribute

UniversalDomainDefinedAttribute	::= SEQUENCE {
	type	UniversalOrBMPString (SIZE (1..ub-domain-defined-attribute-type-length)),
	value	UniversalOrBMPString (SIZE (1..ub-domain-defined-attribute-value-length)) }


-- Upper bounds
-- from MTSUpperBounds { joint-iso-itu-t mhs(6) mts(3) modules(0) upper-bounds(3) version-1999(1) }

ub-common-name-length						INTEGER	::=	64
ub-country-name-alpha-length				INTEGER	::=	2
ub-country-name-numeric-length				INTEGER	::=	3
ub-domain-defined-attribute-type-length		INTEGER	::=	8
ub-domain-defined-attribute-value-length	INTEGER	::=	128
ub-domain-defined-attributes				INTEGER	::=	4
ub-domain-name-length						INTEGER	::=	16
ub-extension-attributes						INTEGER	::=	256
ub-e163-4-number-length						INTEGER	::=	15
ub-e163-4-sub-address-length				INTEGER	::=	40
ub-generation-qualifier-length				INTEGER	::=	3
ub-given-name-length						INTEGER	::=	16
ub-initials-length							INTEGER	::=	5
ub-integer-options							INTEGER	::=	256
ub-numeric-user-id-length					INTEGER	::=	32
ub-organization-name-length					INTEGER	::=	64
ub-organizational-unit-name-length			INTEGER	::=	32
ub-organizational-units						INTEGER	::=	4
ub-pds-name-length							INTEGER	::=	16
ub-pds-parameter-length						INTEGER	::=	30
ub-pds-physical-address-lines				INTEGER	::=	6
ub-postal-code-length						INTEGER	::=	16
ub-surname-length							INTEGER	::=	40
ub-terminal-id-length						INTEGER	::=	24
ub-unformatted-address-length				INTEGER	::=	180
ub-universal-generation-qualifier-length	INTEGER ::= 16
ub-universal-given-name-length				INTEGER ::= 40
ub-universal-initials-length				INTEGER ::= 16
ub-universal-surname-length					INTEGER ::= 64
ub-x121-address-length						INTEGER	::=	16

END
