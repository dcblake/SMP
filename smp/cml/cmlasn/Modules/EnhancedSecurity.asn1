EnhancedSecurity { joint-iso-itu-t ds(5) modules(1) enhancedSecurity(28) 4 }
DEFINITIONS IMPLICIT TAGS  ::=

BEGIN

-- EXPORTS All --

IMPORTS

-- from ITU-T Rec. X.501 | ISO/IEC 9594-2
	authenticationFramework, basicAccessControl, certificateExtensions, id-at, id-avc, id-mr,
	informationFramework, upperBounds
		FROM UsefulDefinitions  -- { joint-iso-itu-t ds(5) module(1) usefulDefinitions(0) 4 }
	Attribute, AttributeType, Context, Name
	-- objectIdentifierMatch , SupportedAttributes
		FROM InformationFramework 

--  See AttributeTypeAndValue below
--	AttributeTypeAndValue
--		FROM BasicAccessControl basicAccessControl

-- from ITU-T Rec. X.509 | ISO/IEC 9594-8
	AlgorithmIdentifier, CertificateSerialNumber --, ENCRYPTED{}, HASH{}, SIGNED{}
		FROM AuthenticationFramework 
	KeyIdentifier  --, GeneralName
		FROM CertificateExtensions 
	ub-privacy-mark-length
		FROM UpperBounds
	GeneralName
		FROM X509Common  ;




-- attributeValueSecurityLabelContext CONTEXT ::= {
--	WITH SYNTAX	SignedSecurityLabel	
--  At most one security label context can be assigned to an
--  attribute value
--	ID			id-avc-attributeValueSecurityLabelContext }

-- TEX SignedSecurityLabel  ::=  SIGNED {SEQUENCE  {
--	attHash		HASH {AttributeTypeAndValue},
--	issuer		Name   		OPTIONAL, name of labelling authority
--	keyIdentifier	KeyIdentifier	OPTIONAL,
--	securityLabel	SecurityLabel } }

-- TEX AttributeTypeAndValue  ::=  SEQUENCE  {
--	type		ATTRIBUTE.&id ({SupportedAttributes}),
--	value  	ATTRIBUTE.&Type({SupportedAttributes}{@type}) }

AttributeTypeAndValue      ::=   SEQUENCE {
    type       OBJECT IDENTIFIER,
    value      ANY }

SignedSecurityLabel ::= SEQUENCE {
	toBeSigned		SignedSecurityLabelToBeSigned,
	algorithm		AlgorithmIdentifier,
	signature		BIT STRING }


AttHash ::= SEQUENCE {
	attributeTypeAndValue	AttributeTypeAndValue,
	algorithmIdentifier		AlgorithmIdentifier,
	hashValue	BIT STRING }

SignedSecurityLabelToBeSigned ::= SEQUENCE {
	attHash			AttHash,
	issuer			Name   		OPTIONAL,  -- name of labelling authority
	keyIdentifier	KeyIdentifier	OPTIONAL,
	securityLabel	SecurityLabel }


SecurityLabel  ::=  SET {
	security-policy-identifier	SecurityPolicyIdentifier   	OPTIONAL,
	security-classification		SecurityClassification		OPTIONAL,
	privacy-mark			PrivacyMark			OPTIONAL,
	security-categories		SecurityCategories		OPTIONAL }
-- TEX	ALL EXCEPT  none at least one component shall be present


SecurityPolicyIdentifier  ::=  OBJECT IDENTIFIER

SecurityClassification ::= INTEGER {
	unmarked		(0),
	unclassified	(1),
	restricted		(2),
	confidential   	(3),
	secret			(4),
	top-secret		(5) }

PrivacyMark  ::=  PrintableString (SIZE (1..ub-privacy-mark-length))

SecurityCategories ::= SET SIZE (1..MAX) OF SecurityCategory

clearance OBJECT-TYPE 
SYNTAX	OldAndNewClearance
	ACCESS	read-write
	STATUS	mandatory
	::=	{id-at-clearance} 

Clearance  ::=  SEQUENCE  {
	policyId			OBJECT IDENTIFIER,
	classList			ClassList DEFAULT {unclassified},
	securityCategories  SecurityCategorySet OPTIONAL  }

SecurityCategorySet  ::=  SET SIZE (1..MAX) OF SecurityCategory


-- REN: 12/12/02:  Note the following OldAndNewClearance production is used
-- to deocde both the old invalid syntax used in DMS and the correct syntax
OldAndNewClearance  ::=  SEQUENCE  {
	policyId			ClearancePolicy,
	classList			Classification OPTIONAL,
	securityCategories  ClearanceCategories OPTIONAL }

ClearancePolicy  ::=  CHOICE  {
	correct	OBJECT IDENTIFIER,
	old		[0] OBJECT IDENTIFIER  }

Classification  ::=  CHOICE  {
	correct	ClassList,
	old		[1] ClassList  }

ClearanceCategories  ::=  CHOICE  {
	correct SecurityCategorySet,
	old		[2] SecurityCategorySet  }


ClassList  ::=  BIT STRING {
	unmarked		(0),
	unclassified	(1),
	restricted		(2),
	confidential  	(3),
	secret			(4),
	topSecret		(5) }

-- TEX SecurityCategory  ::=  SEQUENCE {
--	type		[0]	SECURITY-CATEGORY.&id ({SecurityCategoriesTable}),
--	value   	[1]	EXPLICIT SECURITY-CATEGORY.&Type ({SecurityCategoriesTable} {@type}) }

SecurityCategory ::= SEQUENCE {
	type	[0]	OBJECT IDENTIFIER,
	value	[1]	EXPLICIT ANY DEFINED BY type  }

-- SECURITY-CATEGORY  ::=  TYPE-IDENTIFIER

-- TEX attributeIntegrityInfo ATTRIBUTE  ::=  {
--	WITH SYNTAX				AttributeIntegrityInfo
--	ID						id-at-attributeIntegrityInfo }

-- TEX AttributeIntegrityInfo  ::=  SIGNED { SEQUENCE  {
--	scope		Scope,				Identifies the attributes protected
--	signer		Signer	OPTIONAL,  	Authority or data originators name
--	attribsHash  	AttribsHash } } Hash value of protected attributes

-- TEX AttribsHash  ::=  HASH { SEQUENCE SIZE (1..MAX) OF Attribute }
			-- Attribute type and values with associated context values for the selected Scope

AttributeToBeSigned ::= SEQUENCE SIZE (1..MAX) OF Attribute

AttribsHash ::= SEQUENCE {
	attributeToBeSigned	AttributeToBeSigned,
	algorithmIdentifier		AlgorithmIdentifier,
	hashValue	BIT STRING }

AttributeIntegrityInfoToBeSigned ::= SEQUENCE {
	scope		Scope,				-- Identifies the attributes protected
	signer		Signer	OPTIONAL,  	-- Authority or data originators name
	attribsHash  	AttribsHash } 	-- Hash value of protected attributes

AttributeIntegrityInfo  ::= SEQUENCE {
	toBeSigned 		AttributeIntegrityInfoToBeSigned,	-- Identifies the attributes protected
	algorithm		AlgorithmIdentifier,
	signature		BIT STRING }


Signer  ::=  CHOICE {
	thisEntry	[0]	EXPLICIT ThisEntry,
	thirdParty	[1]	SpecificallyIdentified }

ThisEntry  ::=  CHOICE  {
	onlyOne	NULL,
	specific	IssuerAndSerialNumber }

IssuerAndSerialNumber  ::=  SEQUENCE {
	issuer	Name,
	serial   	CertificateSerialNumber }

SpecificallyIdentified  ::=  SEQUENCE  {
	name   	GeneralName,
	issuer	GeneralName			OPTIONAL,
	serial   	CertificateSerialNumber	OPTIONAL }
--	( WITH COMPONENTS { ..., issuer PRESENT, serial PRESENT } |
--	( WITH COMPONENTS { ..., issuer ABSENT, serial ABSENT } ) )

Scope  ::=  CHOICE  {
	wholeEntry  	[0]	NULL,		-- Signature protects all attribute values in this entry
	selectedTypes	[1]	SelectedTypes
					-- Signature protects all attribute values of the selected attribute types 
	}

SelectedTypes  ::=  SEQUENCE SIZE (1..MAX) OF AttributeType



-- TEX attributeValueIntegrityInfoContext  CONTEXT  ::=  {
--	WITH SYNTAX	AttributeValueIntegrityInfo
--	ID			id-avc-attributeValueIntegrityInfoContext }

-- TEX AttributeValueIntegrityInfo  ::=  SIGNED { SEQUENCE {
--	signer		Signer	OPTIONAL,		Authority or data originators name
--	aVIHash		AVIHash } }  			Hash value of protected attribute

AttributeValueIntegrityInfo  ::=   SEQUENCE {
	signer		Signer	OPTIONAL,	-- Authority or data originators name
	aVIHash		AVIHash,			-- Hash value of protected attribute
	algorithm		AlgorithmIdentifier,
	signature		BIT STRING }

-- TEX AVIHash  ::=  HASH { AttributeTypeValueContexts }
			-- Attribute type and value with associated context values

AVIHash ::= SEQUENCE {
	algorithmIdentifier		AlgorithmIdentifier,
	hashValue	BIT STRING,
	attributeTypeValueContexts	AttributeTypeValueContexts }


-- TEX AttributeTypeValueContexts ::= SEQUENCE {
--	type			ATTRIBUTE.&id ({SupportedAttributes}),
--	value  		ATTRIBUTE.&Type ({SupportedAttributes}{@type}),
--	contextList  	SET SIZE (1..MAX) OF Context OPTIONAL }

AttributeTypeValueContexts ::= SEQUENCE {
	type	OBJECT IDENTIFIER,
	value	ANY,
	contextList	SET SIZE (1..MAX) OF Context OPTIONAL}



id-at-clearance								OBJECT IDENTIFIER	::=	{id-at 55}
-- id-at-defaultDirQop						OBJECT IDENTIFIER	::=	{id-at 56}
id-at-attributeIntegrityInfo				OBJECT IDENTIFIER	::=	{id-at 57}
-- id-at-confKeyInfo						OBJECT IDENTIFIER	::=	{id-at 60}

-- matching rules --
-- id-mr-readerAndKeyIDMatch				OBJECT IDENTIFIER	::=	{id-mr 43}

-- contexts--
id-avc-attributeValueSecurityLabelContext	OBJECT IDENTIFIER	::=	{id-avc 3}
id-avc-attributeValueIntegrityInfoContext	OBJECT IDENTIFIER	::=	{id-avc 4}
END  -- EnhancedSecurity
