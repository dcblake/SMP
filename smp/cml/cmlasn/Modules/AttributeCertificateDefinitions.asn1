AttributeCertificateDefinitions -- {joint-iso-itu-t ds(5) module(1) attributeCertificateDefinitions(32) 4}

DEFINITIONS IMPLICIT TAGS ::=

BEGIN

-- EXPORTS ALL --

IMPORTS
	id-at, id-ce, id-mr, informationFramework, authenticationFramework,
		selectedAttributeTypes, upperBounds, id-oc, certificateExtensions
		FROM UsefulDefinitions -- {joint-iso-itu-t ds(5) module(1) usefulDefinitions(0) 4}

	Name, RelativeDistinguishedName, Attribute, AttributeType
		-- MATCHING-RULE, OBJECT-CLASS, top
		FROM InformationFramework -- informationFramework

	CertificateSerialNumber, CertificateList, AlgorithmIdentifier,
		-- EXTENSION, SIGNED, -- InfoSyntax, PolicySyntax, Extensions, Certificate
		FROM AuthenticationFramework --authenticationFramework

	DirectoryString, TimeSpecification, UniqueIdentifier
		FROM SelectedAttributeTypes --selectedAttributeTypes

	GeneralName, GeneralNames
		FROM X509Common

	NameConstraintsSyntax --, certificateListExactMatch
		FROM CertificateExtensions --certificateExtensions

	ub-name
		FROM UpperBounds --upperBounds

	UserNotice
		FROM PKIXImplicit88

	ORAddress
		FROM ORAddressModule  ;

-- Unless explicitly noted otherwise, there is no significance to the ordering
-- of components of a SEQUENCE OF construct in this specification.

-- attribute certificate constructs --
	
AttributeCertificate	::=	SEQUENCE {
	toBeSigned		AttributeCertificateInfo,
	algorithm		AlgorithmIdentifier,
	signature		BIT STRING }

AttributeCertificateInfo ::= SEQUENCE
	{
	version 				AttCertVersion DEFAULT v1, -- v2 is new standard
	eitherHolder 			CHOICE {
		holder					Holder,		-- if and only if v2
		baseCertificateID		[0]  EXPLICIT IssuerSerial,
		subjectName				[1]  EXPLICIT GeneralNames },			
	issuer					AttCertIssuer,
	signature				AlgorithmIdentifier,
	serialNumber			CertificateSerialNumber,
	attrCertValidityPeriod	AttCertValidityPeriod, 
	attributes				SEQUENCE OF Attribute,
	issuerUniqueID			UniqueIdentifier OPTIONAL,
	extensions				Extensions	OPTIONAL
	}

AttCertVersion	::= INTEGER { v1(0), v2(1) }

			
Holder	::=	SEQUENCE {
	baseCertificateID	[0] IssuerSerial OPTIONAL,
			-- the issuer and serial number of the holder's Public Key Certificate
	entityName			[1] GeneralNames OPTIONAL, 
			-- the name of the entity or role
	objectDigestInfo	[2] ObjectDigestInfo OPTIONAL
			-- used to directly authenticate the holder, e.g. an executable
	-- at least one of baseCertificateID, entityName or objectDigestInfo shall be present
}

ObjectDigestInfo	::= SEQUENCE {
	digestedObjectType		ENUMERATED {
		publicKey				(0),
		publicKeyCert			(1),
		otherObjectTypes		(2) },
	otherObjectTypeID   	OBJECT IDENTIFIER OPTIONAL,
	digestAlgorithm     	AlgorithmIdentifier,
	objectDigest        	BIT STRING }

AttCertIssuer ::= CHOICE {
	v1Form		GeneralNames,		-- v1 only
	v2Form		AttCertIssuerV2		-- v2 only
	}

AttCertIssuerV2	::= [0] SEQUENCE { 
	issuerName				GeneralNames  OPTIONAL,
	baseCertificateID	[0]	IssuerSerial  OPTIONAL,
	objectDigestInfo	[1]	ObjectDigestInfo  OPTIONAL }  
	-- At least one component shall be present
    ( WITH COMPONENTS { ..., issuerName  PRESENT } |
      WITH COMPONENTS { ..., baseCertificateID  PRESENT } |
      WITH COMPONENTS { ..., objectDigestInfo PRESENT } )

IssuerSerial  ::=  SEQUENCE {
	issuer		GeneralNames,
	serial		CertificateSerialNumber,
	issuerUID	UniqueIdentifier OPTIONAL }

AttCertValidityPeriod  ::= SEQUENCE {
	notBeforeTime	GeneralizedTime,
	notAfterTime	GeneralizedTime }

AttributeCertificationPath  ::=  SEQUENCE {
	attributeCertificate		AttributeCertificate, 
	acPath						SEQUENCE OF ACPathData OPTIONAL }

ACPathData  ::=  SEQUENCE {
	certificate				[0]  Certificate OPTIONAL,
	attributeCertificate	[1]  AttributeCertificate OPTIONAL }

PrivilegePolicy	::=	OBJECT IDENTIFIER

-- privilege attributes --

role OBJECT-TYPE	-- ATTRIBUTE
	SYNTAX	RoleSyntax
	ACCESS	read-write
	STATUS	mandatory
	::= {id-at-role}

RoleSyntax	::=	SEQUENCE {
	roleAuthority	[0]	GeneralNames OPTIONAL,
	roleName		[1]	GeneralName }	


-- PMI object classes --
-- DELETED!


-- PMI directory attributes --

attributeCertificateAttribute OBJECT-TYPE	-- ATTRIBUTE
	SYNTAX	AttributeCertificate
	ACCESS	read-write
	STATUS	mandatory
	::= {id-at-attributeCertificate}

aACertificate OBJECT-TYPE	-- ATTRIBUTE
	SYNTAX	AttributeCertificate
	ACCESS	read-write
	STATUS	mandatory
	::= {id-at-aACertificate}

attributeDescriptorCertificate OBJECT-TYPE	-- ATTRIBUTE
	SYNTAX	AttributeCertificate
	ACCESS	read-write
	STATUS	mandatory
	::= {id-at-attributeDescriptorCertificate}

attributeCertificateRevocationList OBJECT-TYPE	-- ATTRIBUTE
	SYNTAX	CertificateList
	ACCESS	read-write
	STATUS	mandatory
	::= {id-at-attributeCertificateRevocationList}

attributeAuthorityRevocationList OBJECT-TYPE	-- ATTRIBUTE
	SYNTAX	CertificateList
	ACCESS	read-write
	STATUS	mandatory
	::= {id-at-attributeAuthorityRevocationList}

delegationPath OBJECT-TYPE	-- ATTRIBUTE
	SYNTAX	AttCertPath
	ACCESS	read-write
	STATUS	mandatory
	::= {id-at-delegationPath}

AttCertPath	::=	SEQUENCE OF AttributeCertificate

privPolicy OBJECT-TYPE	-- ATTRIBUTE
	SYNTAX	PolicySyntax
	ACCESS	read-write
	STATUS	mandatory
	::= {id-at-privPolicy}


-- Attribute certificate extensions and matching rules --
-- Matching rules DELETED!


sOAIdentifier OBJECT-TYPE -- EXTENSION
	SYNTAX	NULL
	ACCESS	read-write
	STATUS	mandatory
	::= {id-ce-sOAIdentifier }

authorityAttributeIdentifier OBJECT-TYPE -- EXTENSION  ::=  {
	SYNTAX	AuthorityAttributeIdentifierSyntax
	ACCESS	read-write
	STATUS	mandatory
	::= {id-ce-authorityAttributeIdentifier }

AuthorityAttributeIdentifierSyntax	::=	SEQUENCE SIZE (1..MAX) OF AuthAttId

AuthAttId	::=	IssuerSerial 

roleSpecCertIdentifier OBJECT-TYPE -- EXTENSION ::=	{
	SYNTAX	RoleSpecCertIdentifierSyntax
	ACCESS	read-write
	STATUS	mandatory
	::= {id-ce-roleSpecCertIdentifier }

RoleSpecCertIdentifierSyntax  ::= SEQUENCE SIZE (1..MAX) OF RoleSpecCertIdentifier

RoleSpecCertIdentifier  ::= SEQUENCE {
	roleName				[0]	GeneralName,
	roleCertIssuer			[1] GeneralName,			
	roleCertSerialNumber	[2] CertificateSerialNumber OPTIONAL,		
	roleCertLocator			[3] GeneralNames OPTIONAL  }

basicAttConstraints OBJECT-TYPE -- EXTENSION ::=  {
	SYNTAX	BasicAttConstraintsSyntax
	ACCESS	read-write
	STATUS	mandatory
	::= {id-ce-basicAttConstraints }

BasicAttConstraintsSyntax ::= SEQUENCE  {
	authority			BOOLEAN DEFAULT FALSE,
	pathLenConstraint 	INTEGER (0..MAX) OPTIONAL  }

delegatedNameConstraints OBJECT-TYPE -- EXTENSION ::= {
	SYNTAX	NameConstraintsSyntax
	ACCESS	read-write
	STATUS	mandatory
	::= {id-ce-delegatedNameConstraints }

timeSpecification OBJECT-TYPE -- EXTENSION  ::=  {
	SYNTAX	TimeSpecification
	ACCESS	read-write
	STATUS	mandatory
	::= {id-ce-timeSpecification}

acceptableCertPolicies OBJECT-TYPE -- EXTENSION ::= {
	SYNTAX	AcceptableCertPoliciesSyntax
	ACCESS	read-write
	STATUS	mandatory
	::= {id-ce-acceptableCertPolicies }

AcceptableCertPoliciesSyntax ::= SEQUENCE SIZE (1..MAX) OF CertPolicyId

CertPolicyId ::= OBJECT IDENTIFIER

attributeDescriptor OBJECT-TYPE -- EXTENSION
	SYNTAX	AttributeDescriptorSyntax
	ACCESS	read-write
	STATUS	mandatory
	::= {id-ce-attributeDescriptor }

AttributeDescriptorSyntax  ::= SEQUENCE {
	identifier 				AttributeIdentifier,
	attributeSyntax			OCTET STRING (SIZE(1..MAX)),
	name  				[0] AttributeName OPTIONAL,
	description			[1] AttributeDescription OPTIONAL,
	dominationRule			PrivilegePolicyIdentifier  }

-- AttributeIdentifier  ::= Attribute.&id({AttributeIDs})
AttributeIdentifier  ::= OBJECT IDENTIFIER

-- AttributeIDs Attribute  ::= {...}

AttributeName  ::= UTF8String(SIZE(1..MAX))

AttributeDescription  ::= UTF8String(SIZE(1..MAX))

PrivilegePolicyIdentifier	::=	SEQUENCE {
	privilegePolicy		PrivilegePolicy,
	privPolSyntax		InfoSyntax }

userNoticeExtension OBJECT-TYPE -- EXTENSION ::= {
	SYNTAX  SEQUENCE SIZE (1..MAX) OF UserNotice
	ACCESS	read-write
	STATUS	mandatory
	::= { id-ce-userNotice }
	
targetingInformation OBJECT-TYPE --  EXTENSION  ::= {
	SYNTAX  SEQUENCE SIZE (1..MAX) OF Targets
	ACCESS	read-write
	STATUS	mandatory
	::= { id-ce-targetInformation }

Targets	::=	SEQUENCE SIZE (1..MAX) OF Target

Target	::=	CHOICE {
	targetName		[0]	GeneralName,
	targetGroup		[1]	GeneralName,
	targetCert		[2]	TargetCert }

TargetCert	::=	SEQUENCE {
	targetCertificate	IssuerSerial,
	targetName			GeneralName OPTIONAL,
	certDigestInfo		ObjectDigestInfo OPTIONAL }

noRevAvail OBJECT-TYPE -- EXTENSION ::=  {
	SYNTAX  NULL
	ACCESS	read-write
	STATUS	mandatory
	::= { id-ce-noRevAvail }

acceptablePrivilegePolicies OBJECT-TYPE -- EXTENSION ::= {
	SYNTAX	AcceptablePrivilegePoliciesSyntax
	ACCESS	read-write
	STATUS	mandatory
	::= { id-ce-acceptablePrivilegePolicies }

AcceptablePrivilegePoliciesSyntax	::=	SEQUENCE SIZE (1..MAX) OF PrivilegePolicy


--object identifier assignments-

--object classes-

id-oc-pmiUser						OBJECT IDENTIFIER ::=		{id-oc 24}
id-oc-pmiAA							OBJECT IDENTIFIER ::=		{id-oc 25}
id-oc-pmiSOA						OBJECT IDENTIFIER ::=		{id-oc 26}
id-oc-attCertCRLDistributionPts		OBJECT IDENTIFIER ::=		{id-oc 27}
id-oc-privilegePolicy				OBJECT IDENTIFIER ::=		{id-oc 32}
id-oc-pmiDelegationPath				OBJECT IDENTIFIER ::=		{id-oc 33}


--directory attributes--

id-at-attributeCertificate					OBJECT IDENTIFIER	::=	{id-at 58}
id-at-attributeCertificateRevocationList	OBJECT IDENTIFIER ::=	{id-at 59}
id-at-aACertificate							OBJECT IDENTIFIER ::=	{id-at 61}
id-at-attributeDescriptorCertificate		OBJECT IDENTIFIER ::=	{id-at 62}
id-at-attributeAuthorityRevocationList		OBJECT IDENTIFIER ::=	{id-at 63}
id-at-privPolicy							OBJECT IDENTIFIER ::=	{id-at 71}
id-at-role									OBJECT IDENTIFIER ::=	{id-at 72}
id-at-delegationPath						OBJECT IDENTIFIER ::=	{id-at 73}


--attribute certificate extensions-

id-ce-authorityAttributeIdentifier		OBJECT IDENTIFIER ::=	{id-ce 38}
id-ce-roleSpecCertIdentifier			OBJECT IDENTIFIER ::=	{id-ce 39}
id-ce-basicAttConstraints				OBJECT IDENTIFIER ::=	{id-ce 41}
id-ce-delegatedNameConstraints			OBJECT IDENTIFIER ::=	{id-ce 42}
id-ce-timeSpecification					OBJECT IDENTIFIER ::=	{id-ce 43}
id-ce-attributeDescriptor				OBJECT IDENTIFIER ::=	{id-ce 48}
id-ce-userNotice						OBJECT IDENTIFIER ::=	{id-ce 49}
id-ce-sOAIdentifier						OBJECT IDENTIFIER ::=	{id-ce 50}
id-ce-acceptableCertPolicies			OBJECT IDENTIFIER ::=	{id-ce 52}
id-ce-targetInformation					OBJECT IDENTIFIER ::=	{id-ce 55}
id-ce-noRevAvail						OBJECT IDENTIFIER ::=	{id-ce 56}
id-ce-acceptablePrivilegePolicies		OBJECT IDENTIFIER ::=	{id-ce 57}


--PMI matching rules--

id-mr-attributeCertificateMatch				OBJECT IDENTIFIER ::=	{id-mr 42}
id-mr-attributeCertificateExactMatch		OBJECT IDENTIFIER ::=	{id-mr 45}
id-mr-holderIssuerMatch						OBJECT IDENTIFIER ::=	{id-mr 46}
id-mr-authAttIdMatch						OBJECT IDENTIFIER ::=	{id-mr 53}
id-mr-roleSpecCertIdMatch					OBJECT IDENTIFIER ::=	{id-mr 54}
id-mr-basicAttConstraintsMatch				OBJECT IDENTIFIER ::=	{id-mr 55}
id-mr-delegatedNameConstraintsMatch			OBJECT IDENTIFIER ::=	{id-mr 56}
id-mr-timeSpecMatch							OBJECT IDENTIFIER ::=	{id-mr 57}
id-mr-attDescriptorMatch					OBJECT IDENTIFIER ::=	{id-mr 58}
id-mr-acceptableCertPoliciesMatch			OBJECT IDENTIFIER ::=	{id-mr 59}
id-mr-delegationPathMatch					OBJECT IDENTIFIER ::=	{id-mr 61}



END
