AuthenticationFramework -- {joint-iso-ccitt ds(5) module(1) authenticationFramework(7) 4}

DEFINITIONS ::=

BEGIN

-- EXPORTS All --

-- The types and values defined in this module are exported for use in the other ASN.1 modules contained 
-- within the Directory Specifications, and for the use of other applications which will use them to access 
-- Directory services. Other applications may use them for their own purposes, but this will not constrain
-- extensions and modifications needed to maintain or improve the Directory service.

IMPORTS
	id-at, id-nf, id-oc, informationFramework, upperBounds, selectedAttributeTypes,
	basicAccessControl, certificateExtensions
		FROM UsefulDefinitions -- {joint-iso-itu-t ds(5) module(1) usefulDefinitions(0) 4}

	Name --, ATTRIBUTE, OBJECT-CLASS, NAME-FORM, top
		FROM InformationFramework

	ub-user-password, ub-content
		FROM UpperBounds

	UniqueIdentifier, -- octetStringMatch,-- DirectoryString, commonName, pkcs
		FROM SelectedAttributeTypes

	KeyUsage, GeneralNames, CertificatePoliciesSyntax, CertPolicyId1
		FROM X509Common  ;


--public-key certificate definition--

Certificate		::=	--snacc isPdu:"TRUE" -- SEQUENCE {
	toBeSigned		CertificateToBeSigned,
	algorithm		AlgorithmIdentifier,
	signature		BIT STRING }

CertificateToBeSigned	::= SEQUENCE {
	version					[0]	Version DEFAULT v1,
	serialNumber				CertificateSerialNumber,
	signature					AlgorithmIdentifier,
	issuer						Name,
	validity					Validity,
	subject						Name,
	subjectPublicKeyInfo		SubjectPublicKeyInfo,
	issuerUniqueIdentifier	[1]	IMPLICIT UniqueIdentifier OPTIONAL,
								-- if present, version must be v2 or v3
	subjectUniqueIdentifier	[2]	IMPLICIT UniqueIdentifier OPTIONAL,
								-- if present, version must be v2 or v3
	extensions				[3]	Extensions OPTIONAL
								-- If present, version must be v3 -- }

Version				::=	INTEGER { v1(0), v2(1), v3(2) }

CertificateSerialNumber	::=	INTEGER	

AlgorithmIdentifier	::= SEQUENCE {
	algorithm	OBJECT IDENTIFIER,
	parameters	ANY DEFINED BY algorithm OPTIONAL }

-- AlgorithmIdentifier	::= SEQUENCE {
--	algorithm	ALGORITHM.&id({SupportedAlgorithms}),
--	parameters	ALGORITHM.&Type({SupportedAlgorithms}{@algorithm}) OPTIONAL }

--	Definition of the following information object set is deferred, perhaps to standardized
--	profiles or to protocol implementation conformance statements. The set is required to
--	specify a table constraint on the parameters component of AlgorithmIdentifier.
-- SupportedAlgorithms ALGORITHM	::=  {...}

Validity	::=	SEQUENCE {
	notBefore	Time,
	notAfter	Time }

SubjectPublicKeyInfo	::=	SEQUENCE {
	algorithm			AlgorithmIdentifier,
	subjectPublicKey	BIT STRING }

Time  ::=  CHOICE { 
	utcTime 		UTCTime, 
	generalizedTime	GeneralizedTime }

Extensions ::= SEQUENCE OF Extension
-- For those extensions where ordering of individual extensions within the SEQUENCE is significant, the
-- specification of those individual extensions shall include the rules for the significance of the order therein

Extension	::= SEQUENCE {
	extnId		OBJECT IDENTIFIER,
	critical	BOOLEAN DEFAULT FALSE,
	extnValue	OCTET STRING CONTAINING ANY DEFINED BY extnId -- OCTET STRING --
				-- contains a DER encoding of a value of type &ExtnType
				-- for the extension object identified by extnId -- }

-- ExtensionSet	EXTENSION	::=	{  ... }

-- EXTENSION ::= CLASS {
--	&id		OBJECT IDENTIFIER UNIQUE,
--	&ExtnType }
-- WITH SYNTAX {
--	SYNTAX		&ExtnType
--	IDENTIFIED BY	&id }


-- other PKI certifiate constructs

Certificates	::=	--snacc isPdu:"TRUE" -- SEQUENCE {
	userCertificate		Certificate,
	certificationPath	ForwardCertificationPath OPTIONAL }

ForwardCertificationPath	::=	SEQUENCE OF CrossCertificates

CrossCertificates		::=	SET OF Certificate

PkiPath		::= SEQUENCE OF Certificate

CertificationPath	::=	--snacc isPdu:"TRUE" -- SEQUENCE {
	userCertificate		Certificate,
	theCACertificates	SEQUENCE OF CertificatePair OPTIONAL }

CertificatePair	::=	--snacc isPdu:"TRUE" -- SEQUENCE {
	forward		[0]	Certificate OPTIONAL,
	reverse		[1]	Certificate OPTIONAL
					-- at least one of the pair shall be present -- }


AnySignedPath	::= --snacc isPdu:"TRUE" -- SEQUENCE {
	userCertificate		SignedObject,
	theCACertificates	SEQUENCE OF AnySignedPair OPTIONAL }

AnySignedPair	::=	--snacc isPdu:"TRUE" -- SEQUENCE {
	forward		[0]	SignedObject OPTIONAL,
	reverse		[1]	SignedObject OPTIONAL
					-- at least one of the pair shall be present -- }


-- certificate revocation list (CRL)

CertificateList		::=	--snacc isPdu:"TRUE" -- SEQUENCE { 
	toBeSigned		CertificateListToBeSigned,
	algorithm		AlgorithmIdentifier,
	signature		BIT STRING }

CertificateListToBeSigned		::= SEQUENCE {
	version					Version OPTIONAL,
							-- if present, version shall be v2
	signature				AlgorithmIdentifier,
	issuer					Name,
	thisUpdate				Time,
	nextUpdate				Time OPTIONAL,
	revokedCertificates		SEQUENCE OF SEQUENCE {
		serialNumber			CertificateSerialNumber,
		revocationDate			Time,
		crlEntryExtensions		Extensions OPTIONAL } OPTIONAL,
	crlExtensions		[0]	Extensions OPTIONAL }


-- information object classes --

-- ALGORITHM	::=	TYPE-IDENTIFIER

-- parameterized types --
-- HASH {ToBeHashed}	::=	SEQUENCE {
--	algorithmIdentifier		AlgorithmIdentifier,
--	hashValue			BIT STRING ( CONSTRAINED BY {
	-- must be the result of applying a hashing procedure to the DER-encoded octets --
	-- of a value of ToBeHashed } ) }

-- ENCRYPTED-HASH { ToBeSigned }	::=	BIT STRING ( CONSTRAINED BY {
	-- must be the result of applying a hashing procedure to the DER-encoded (see 6.1) octets --
	-- of a value of ToBeSigned and then applying an encipherment procedure to those octets })

-- ENCRYPTED { ToBeEnciphered }	::=	BIT STRING ( CONSTRAINED BY {
	-- must be the result of applying an encipherment procedure --
	-- to the BER-encoded octets of a value of ToBeEnciphered})

-- SIGNATURE { ToBeSigned }		::=	SEQUENCE {
--	algorithmIdentifier		AlgorithmIdentifier,
--	encrypted			ENCRYPTED-HASH { ToBeSigned }}

-- SIGNED { ToBeSigned }		::=	SEQUENCE {
--	toBeSigned			ToBeSigned,
--	COMPONENTS OF		SIGNATURE { ToBeSigned }}

SignedObject	::= --snacc isPdu:"TRUE" -- SEQUENCE {
	toBeSigned				ANY,
	algorithmIdentifier		AlgorithmIdentifier,
	encrypted				BIT STRING  }



-- PKI object classes --
-- DELETED!


-- PKI directory attributes -
-- DELETED the attributes, but left the following definitions
-- for SupportedAlgorithm, InfoSyntax, HashedPolicyInfo, PolicySyntax, PolicyID

SupportedAlgorithm ::= SEQUENCE {
  	algorithmIdentifier				AlgorithmIdentifier,
	intendedUsage				[0]	KeyUsage OPTIONAL,
	intendedCertificatePolicies	[1]	CertificatePoliciesSyntax OPTIONAL }

InfoSyntax	::=	CHOICE {
	content		DirectoryString (SIZE (1..ub-content)), -- {ub-content}
	pointer		SEQUENCE {
		name		GeneralNames,
		hash		SEQUENCE {
			algorithmIdentifier	AlgorithmIdentifier,
			hashValue			BIT STRING } OPTIONAL } }
								-- hash of HashedPolicyInfo 

HashedPolicyInfo	::= ANY

PolicySyntax	::=	SEQUENCE {
	policyIdentifier	PolicyID,
	policySyntax		InfoSyntax	}

PolicyID	::=	OBJECT IDENTIFIER	


-- object identifier assignments --

-- object classes --
-- DELETED!

-- name forms --
-- DELETED!

-- directory attributes --
id-at-userPassword				OBJECT IDENTIFIER	::=	{id-at 35} 
id-at-userCertificate			OBJECT IDENTIFIER	::=	{id-at 36}
id-at-cAcertificate				OBJECT IDENTIFIER	::=	{id-at 37}
id-at-authorityRevocationList	OBJECT IDENTIFIER	::=	{id-at 38}
id-at-certificateRevocationList	OBJECT IDENTIFIER	::=	{id-at 39}
id-at-crossCertificatePair		OBJECT IDENTIFIER	::=	{id-at 40}
id-at-supportedAlgorithms		OBJECT IDENTIFIER	::=	{id-at 52}
id-at-deltaRevocationList		OBJECT IDENTIFIER	::=	{id-at 53}
id-at-certificationPracticeStmt	OBJECT IDENTIFIER 	::=	{id-at 68}
id-at-certificatePolicy			OBJECT IDENTIFIER 	::=	{id-at 69}
id-at-pkiPath					OBJECT IDENTIFIER	::=	{id-at 70}


END
